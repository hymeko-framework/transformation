// SysML v2 structural model, generated by HyMeKo for {{config:robot_name}}.
//
// Type-level projection of one signed-hypergraph IR (vocabulary:
// data/sysml/meta_sysml_structure.hymeko):
//   - `part def` per block; `:>` only for bases that are themselves blocks
//   - `port def <Owner>_<port>` per port declared inside a block
//   - composition (+ whole, - part) as a connection def with end multiplicities
//   - n-ary connector (+ source port, - target port, ~ items / medium) as a
//     connection def; the neutral participants are kept in its doc
//   - deployment: nodes, environments, artifacts and procured products as part defs, realizes / hosts as
//     allocations, the n-ary deploys edge as one allocation def
// Part usages are not instantiated per role (type-level IBD). The output has
// not been checked by a SysML v2 tool.

package {{config:robot_name}} {

    // ── Items and media ───────────────────────────────────────────
{{#each items}}
    item def {{name}};
{{/each}}
{{#each media}}
    item def {{name}};
{{/each}}

    // ── Blocks ────────────────────────────────────────────────────
{{#each blocks}}
    part def {{name}}{{#if bases:blocks}} :> {{bases:blocks}}{{/if}};
{{/each}}

    // ── Ports ─────────────────────────────────────────────────────
{{#each ports}}
    port def {{owner}}_{{name}};
{{/each}}

    // ── Composition (+ whole, - part) ─────────────────────────────
{{#each composes_edges}}
    connection def {{name}} {
        end whole : {{bind:+:0}}[1];
        end {{field:role}} : {{bind:-:0}}{{#if field:lower}}[{{field:lower}}..{{field:upper}}]{{/if}}{{#if field:mult}}[{{field:mult.lower}}..{{field:mult.upper}}]{{/if}};
    }
{{/each}}

    // ── Connectors (+ source port, - target port, ~ conveyed) ─────
{{#each connects_edges}}
    connection def {{name}} {
        end source : {{bindowner:+:0}}_{{bind:+:0}};
        end target : {{bindowner:-:0}}_{{bind:-:0}};
        doc /* conveys: {{bind:~:all_csv}} */
    }
{{/each}}

    // ── Deployment ────────────────────────────────────────────────
{{#each nodes}}
    part def {{name}};
{{/each}}
{{#each envs}}
    part def {{name}};
{{/each}}
{{#each artifacts}}
    part def {{name}};
{{/each}}
    // Procured products: realizes (+ product, - block) becomes an allocation below.
{{#each products}}
    part def {{name}};
{{/each}}
{{#each realizes_edges}}
    allocate {{bind:-:0}} to {{bind:+:0}};
{{/each}}
{{#each hosts_edges}}
    allocate {{bind:-:0}} to {{bind:+:0}};
{{/each}}
{{#each deploys_edges}}
    allocation def {{name}} {
        doc /* deploys {{bind:-:all_csv}} to {{bind:+:0}} */
    }
{{/each}}
}
